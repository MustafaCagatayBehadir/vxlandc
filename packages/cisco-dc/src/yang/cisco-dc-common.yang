submodule cisco-dc-common {
    belongs-to cisco-dc {
        prefix "cisco-dc";
    }

    yang-version 1.1;

    import tailf-common {
        prefix tailf;
    }
    import tailf-ncs {
        prefix ncs;
    }

    revision 2022-01-17 {
        description
          "Initial Revision.";
    }

    typedef dc-string {
        type string {
            pattern
              '[^\s]+' {
                error-message
                  "No space/s allowed.";
            }
        }
    }

    typedef node-port {
        type string {
            pattern
              '[1-9]/[1-9][0-9]{0,1}';
        }
    }

    typedef vlan {
        type uint16 {
            range "1..4094";
        }
        description
          "Typedef for VLAN";
    }

    typedef vxlan-id {
        type uint32;
        description
          "Typedef for VxLAN ID.";
    }

    typedef loopback-id {
        type uint8 {
            range 100..200;
        }
    }

    typedef mtu {
        type uint16 {
            range 68..9216;
        }
    }

    typedef route-target {
        type string {
            pattern
              '((6553[0-5]|655[0-2][0-9]|65[0-4][0-9]{2}|'
            + '6[0-4][0-9]{3}|'
            + '[1-5][0-9]{4}|[1-9][0-9]{0,3}|0):(429496729[0-5]|'
            + '42949672[0-8][0-9]|'
            + '4294967[01][0-9]{2}|429496[0-6][0-9]{3}|'
            + '42949[0-5][0-9]{4}|'
            + '4294[0-8][0-9]{5}|429[0-3][0-9]{6}|'
            + '42[0-8][0-9]{7}|4[01][0-9]{8}|'
            + '[1-3][0-9]{9}|[1-9][0-9]{0,8}|0))|'
            + '((429496729[0-5]|42949672[0-8][0-9]|'
            + '4294967[01][0-9]{2}|429496[0-6][0-9]{3}|'
            + '42949[0-5][0-9]{4}|'
            + '4294[0-8][0-9]{5}|429[0-3][0-9]{6}|'
            + '42[0-8][0-9]{7}|4[01][0-9]{8}|'
            + '[1-3][0-9]{9}|[1-9][0-9]{0,8}|0):(6553[0-5]|'
            + '655[0-2][0-9]|65[0-4][0-9]{2}|6[0-4][0-9]{3}|'
            + '[1-5][0-9]{4}|[1-9][0-9]{0,3}|0))';
        }
        description
          "A route target is an 8-octet BGP extended community
           initially identifying a set of sites in a BGP
           VPN (RFC 4364).  This type definition supports both
           type0 (2-octet-asn:4-octet-number) and
           type2 (4-octet-asn:2-octet-number) patterns as supported
           by Cisco NX-OS";
    }
}
