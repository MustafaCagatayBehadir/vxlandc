submodule cisco-dc-tenant {

    belongs-to cisco-dc {
        prefix "cisco-dc";
    }

    yang-version 1.1;

    import ietf-inet-types {
        prefix inet;
    }

    import tailf-common {
        prefix tailf;
    }

    import tailf-ncs {
        prefix ncs;
    }

    include cisco-dc-common {
        revision-date "2022-01-17";
    }

    description
      "VXLAN EVPN Datacenter Customer Tenants";

    revision 2022-01-17 {
        description
          "Initial revision.";
    }

    grouping tenant-service {

        leaf name {
            type dc-string;
            tailf:info "Specify tenant name as Service";
        }

        leaf description {
            type string;
            tailf:info "Tenant Description";
        }
    }

    grouping bridge-domain {

        leaf name {
            tailf:info "Specify bridge domain name";
            type dc-string;
        }

        tailf:validate "bridge-domain-service-validation" {
            tailf:dependency "bd-subnet";
        }

        container l2vni {
            tailf:info "Layer 2 VNI Configuration Parameters";

            leaf vlan-id {
                tailf:info "Vlan id is allocated by resource-manager, use this field to overwrite the default behavior.";
                type vlan;
            }

            leaf vni-id {
                tailf:info "Vni id is allocated by resource-manager, use this field to overwrite the default behavior.";
                type vxlan-id;
            }
        }

        list port-group {
            tailf:info "Attach port group defined in fabric";

            key name;

            leaf name {
                tailf:info "Port Group Name";
                type leafref {
                    path "/cisco-dc:dc-site[cisco-dc:fabric=current()/../../../../fabric]/cisco-dc:port-configs/cisco-dc:name";
                }
            }

            leaf mode {
                must "current() = deref(current()/../name)/../cisco-dc:mode" {
                    tailf:dependency ".";
                    tailf:dependency "../name";
                    error-message
                      "Port group mode must match with the tenant-service encap mode";
                }
                tailf:info "Port Mode.It can be Access | Trunk";
                type enumeration {
                    enum access;
                    enum trunk;
                }
                mandatory true;
            }

            must "count(/cisco-dc:dc-site[cisco-dc:fabric=current()/../site]/cisco-dc:tenant-service/cisco-dc:bridge-domain/port-group[cisco-dc:name=current()/name]) = 1 or "
            + "current()/mode = 'trunk'" {
                error-message
                  "Access port-group can not be added more than one bridge-domain.";
            }
        }

        list device {
            tailf:hidden "Attach device defined in infra by bd service";
            key "kp leaf-id";

            leaf kp {
                tailf:info "Attach port keypath";
                type string;
            }

            leaf leaf-id {
                tailf:info "Define Leaf Node ID";
                type string;
            }

            leaf network-vlan {
                tailf:info "Define network vlan value";
                type vlan;
                tailf:default-ref "../../cisco-dc:vlan-id";
            }

            leaf l2vni {
                tailf:info "L2 Vni id is allocated by resource-manager";
                type vxlan-id;
                tailf:default-ref "../../cisco-dc:vni-id";
            }
        }

        list bd-subnet {
            tailf:info "Specify Bridge Domain subnet address & scope";
            key address;

            leaf address {
                tailf:info "A.B.C.D/L;;Prefix or X:X::X/L;;Prefix for L3 Internal Subnet";
                type tailf:ip-address-and-prefix-length;
            }

            leaf preferred {
                tailf:info "Specify preferred value [yes] for primary ip address.";
                type enumeration {
                    enum yes;
                    enum no;
                }
                default no;
            }

            leaf address-family {
                tailf:hidden "dc";
                type enumeration {
                    enum ipv4;
                    enum ipv6;
                }
            }
        }

        leaf mtu {
            when "../bd-subnet";
            tailf:info "Set the interface Maximum Transmission Unit (MTU)";
            type mtu;
        }

        leaf vrf {
            when "../bd-subnet";
            tailf:info "Associate VRF on Bridge Domain";
            type leafref {
                path "../../../cisco-dc:vrf-config/cisco-dc:name";
            }
            mandatory true;

            must "/cisco-dc:dc-site[cisco-dc:fabric=current()/../site]/cisco-dc:vrf-config[cisco-dc:name=current()]/cisco-dc:approved='true'" {
                error-message
                  "Vrf approved should be set to true before adding to bridge-domain";
            }
        }

        leaf vlan-id {
            tailf:hidden "Just for convenience";
            type vlan;
        }

        leaf vni-id {
            tailf:hidden "Just for convenience";
            type vxlan-id;
        }

        leaf site {
            tailf:hidden "Just for convenience";
            type string;
            tailf:default-ref "../../../cisco-dc:fabric";
        }

        leaf mcast-group {
            tailf:hidden "Just for convenience";
            type inet:ipv4-address;
            tailf:default-ref "../../../cisco-dc:fabric-parameters/cisco-dc:mcast-group";
        }

        leaf tenant {
            tailf:hidden "Just for convenience";
            type string;
            tailf:default-ref "../../cisco-dc:name";
        }

        leaf id-allocated {
            tailf:hidden "dc";
            type boolean;
            default false;
        }

        leaf approved {
            tailf:info "Approved will set to true if id is allocated";
            type boolean;
            default false;
        }
    }
}
