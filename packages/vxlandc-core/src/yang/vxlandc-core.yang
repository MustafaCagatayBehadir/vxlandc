module vxlandc-core {

    yang-version 1.1;
    namespace "http://turkcell.com.tr/vxlandc-core";
    prefix vxlandc-core;

    import ietf-inet-types {
        prefix inet;
    }
    import tailf-common {
        prefix tailf;
    }
    import tailf-ncs {
        prefix ncs;
    }
    import resource-allocator {
        prefix ralloc;
    }
    import id-allocator {
        prefix idalloc;
    }

    description
      "VXLAN EVPN Datacenter Environment";

    revision 2022-01-17 {
        description
          "Initial revision.";
    }

    grouping site-tenants {

        container tenants {

            list tenant {
                description
                  "List of Data Center customer definitions";
                tailf:info "Define Data Center customer data";
                key name;
                must "count(../tenant[translate(name,'abcdefghijklmnopqrstuvwxyz','ABCDEFGHIJKLMNOPQRSTUVWXYZ')=translate(current()/name,'abcdefghijklmnopqrstuvwxyz','ABCDEFGHIJKLMNOPQRSTUVWXYZ')])=1" {
                    error-message
                      "tenant name needs to be unique without case sensitivity";
                    tailf:dependency "./name";
                    tailf:override-auto-dependencies;
                }
                leaf name {
                    type string;
                    tailf:info "Tenant Name";
                }

                leaf id {
                    type string;
                    tailf:info "Unique Tenant ID";
                }

                leaf description {
                    type string;
                    tailf:info "Tenant Description";
                }
            }
        }
    }

    grouping sites {

        container sites {

            list site {
                key fabric;

                leaf fabric {
                    tailf:info "Data Center Fabric Name";
                    type string;
                }

                list node {
                    key hostname;

                    leaf hostname {
                        tailf:info "Node hostname";
                        type leafref {
                            path "/ncs:devices/ncs:device/ncs:name";
                        }
                    }

                    leaf node-role {
                        tailf:info "Node role in the fabric";
                        type enumeration {
                            enum access-leaf;
                            enum border-leaf;
                            enum spine;
                        }
                    }

                    leaf node-type {
                        when "../node-role != 'spine'";
                        tailf:info "Node type can be vPC or standalone";
                        type enumeration {
                            enum standalone;
                            enum vPC;
                        }
                        mandatory true;
                    }

                    leaf po-id-pool {
                        tailf:info "Port Channel ID Pool Name";
                        type leafref {
                            path "/ralloc:resource-pools/idalloc:id-pool/idalloc:name";
                        }
                    }
                }

                list node-group {
                    key id;
                    unique "node-1 node-2";

                    leaf id {
                        tailf:info "VPC Domain ID";
                        type uint16 {
                            range "1..1000";
                        }
                        tailf:cli-suppress-range;
                    }

                    leaf node-1 {
                        must "/vxlandc-core:vxlandc/vxlandc-core:sites/vxlandc-core:site[vxlandc-core:fabric=current()/../../vxlandc-core:fabric]"
                        + "/vxlandc-core:node[vxlandc-core:hostname=current()]/vxlandc-core:node-type = 'vPC'" {
                            error-message
                              "Node type must be vPC";
                        }
                        tailf:info "VPC Node 1 hostname";
                        type leafref {
                            path "/ncs:devices/ncs:device/ncs:name";
                        }
                        mandatory true;
                    }

                    leaf node-2 {
                        must "/vxlandc-core:vxlandc/vxlandc-core:sites/vxlandc-core:site[vxlandc-core:fabric=current()/../../vxlandc-core:fabric]"
                        + "/vxlandc-core:node[vxlandc-core:hostname=current()]/vxlandc-core:node-type = 'vPC'" {
                            error-message
                              "Node type must be vPC";
                        }
                        tailf:info "VPC Node 2 hostname";
                        type leafref {
                            path "/ncs:devices/ncs:device/ncs:name";
                        }
                        mandatory true;
                    }

                    leaf po-id-pool {
                        tailf:info "Port Channel ID Pool Name";
                        type leafref {
                            path "/ralloc:resource-pools/idalloc:id-pool/idalloc:name";
                        }
                    }
                }

                container connections {
                    leaf uplink-to-dci-gw-01 {
                        tailf:info "Port-Channel interface id on the border leaf to DCI-GW-01";
                        type uint16 {
                            range "1..9999";
                        }
                        mandatory true;
                    }

                    leaf uplink-to-dci-gw-02 {
                        tailf:info "Port-Channel interface id on the border leaf to DCI-GW-02";
                        type uint16 {
                            range "1..9999";
                        }
                        mandatory true;
                    }
                }

                container fabric-parameters {
                    leaf as-number {
                        tailf:info "BGP AS Number of the Site";
                        type inet:as-number;
                        mandatory true;
                    }

                    leaf mcast-group {
                        tailf:info "Multicast Group for VXLAN Overlay";
                        type inet:ipv4-address;
                        mandatory true;
                    }
                }

                container resource-pools {
                    leaf l2-network-vlan {
                        tailf:info "Layer 2 Network Vlan Pool";
                        type leafref {
                            path "/ralloc:resource-pools/idalloc:id-pool/idalloc:name";
                        }
                    }

                    leaf l3-vrf-vlan {
                        tailf:info "Layer 3 VRF Vlan Pool";
                        type leafref {
                            path "/ralloc:resource-pools/idalloc:id-pool/idalloc:name";
                        }
                    }
                    leaf l2-vxlan-vni {
                        tailf:info "Layer 2 VXLAN VNI Pool";
                        type leafref {
                            path "/ralloc:resource-pools/idalloc:id-pool/idalloc:name";
                        }
                    }

                    leaf l3-vxlan-vni {
                        tailf:info "Layer 3 VXLAN VNI Pool";
                        type leafref {
                            path "/ralloc:resource-pools/idalloc:id-pool/idalloc:name";
                        }
                    }
                }

                uses site-tenants;
            }
        }
    }

    grouping site-operations {

        container sites-operations {

            container site-discovery {
                tailf:action discover-site {
                    tailf:actionpoint discover-site;
                    description
                      "Action to add devices to NSO and create fabric environment";
                    input {
                        leaf site {
                            tailf:info "Site name for discovery";
                            type leafref {
                                path "/vxlandc-core:vxlandc/vxlandc-core:sites/vxlandc-core:site/vxlandc-core:fabric";
                            }
                        }
                        leaf spine {
                            must "contains(., 'SPN')" {
                                error-message
                                  "Node must be a spine node";
                                tailf:dependency ".";
                            }
                            tailf:info "Spine name for discover the fabric";
                            type leafref {
                                path "/ncs:devices/ncs:device/ncs:name";
                            }
                        }
                    }
                    output {
                        leaf success {
                            type boolean;
                        }
                    }
                }
            }

            container resource-pools {
                tailf:action create-site-resource-pools {
                    tailf:actionpoint create-site-resource-pools;
                    description
                      "Action to create resource-pools for selected site";
                    input {
                        list id-pool {
                            key "id";

                            leaf id {
                                tailf:info "Pool Name. Can be l2-vxlan-vni | l3-vxlan-vni | network-vlan | vrf-vlan";
                                type enumeration {
                                    enum l2-vxlan-vni;
                                    enum l3-vxlan-vni;
                                    enum l2-network-vlan;
                                    enum l3-vrf-vlan;
                                    enum port-channel-id;
                                }
                            }

                            leaf start {
                                type uint32;
                                mandatory true;
                            }

                            leaf end {
                                type uint32;
                                mandatory true;
                                must ". >= ../start" {
                                    error-message
                                      "range end must be greater or equal to range start";
                                    tailf:dependency "../start";
                                }
                            }

                            leaf scope {
                                tailf:info "Id Pool Scope. Can be fabric | local";
                                type enumeration {
                                    enum fabric;
                                    enum local;
                                }
                            }
                        }

                        leaf site {
                            tailf:info "Site name";
                            type leafref {
                                path "/vxlandc-core:vxlandc/vxlandc-core:sites/vxlandc-core:site/vxlandc-core:fabric";
                            }
                        }
                    }

                    output {
                        leaf success {
                            type boolean;
                        }
                    }
                }
            }
        }
    }

    container vxlandc {

        uses sites;

        uses site-operations;
    }
}
