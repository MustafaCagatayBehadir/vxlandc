module cisco-dc {

    yang-version 1.1;
    namespace "http://turkcell.com.tr/cisco-dc";
    prefix cisco-dc;

    import ietf-inet-types {
        prefix inet;
    }
    import tailf-common {
        prefix tailf;
    }
    import tailf-ncs {
        prefix ncs;
    }
    import tailf-kicker {
        prefix kicker;
    }

    include cisco-dc-common {
        revision-date "2022-01-17";
    }

    include cisco-dc-nano-services {
        revision-date "2022-01-17";
    }

    include cisco-dc-site {
        revision-date "2022-01-17";
    }

    include cisco-dc-tenant {
        revision-date "2022-01-17";
    }

    include cisco-dc-port-config {
        revision-date "2022-01-17";
    }

    include cisco-dc-vrf-config {
        revision-date "2022-01-17";
    }

    include cisco-dc-routepolicy {
        revision-date "2022-01-17";
    }

    include cisco-dc-l3out-routing {
        revision-date "2022-01-17";
    }

    description
      "Cisco VXLAN EVPN Datacenter";

    revision 2022-03-15 {
        description
          "Initial revision.";
    }

    list dc-site {
        tailf:info "Specify DataCenter site fabric name";

        key fabric;

        uses site-configs;

        tailf:validate "tenant-service-validation" {
            tailf:dependency "tenant-service/name";
        }

        list tenant-service {
            description
              "List of Data Center customer definitions";
            tailf:info "Deploy a tenant service";

            key name;

            uses tenant-service;

            list bridge-domain {
                tailf:info "Define Bridge Domain Name";

                uses ncs:nano-plan-data;
                uses ncs:service-data;
                ncs:servicepoint bridge-domain-config-servicepoint;

                key name;

                uses bridge-domain;

                uses l3out-routing {
                    when "bd-subnet";

                    refine routing/l3out-type {
                        default fabric-internal;
                    }

                    refine routing/bgp/ttl {
                        default 5;
                    }

                    refine routing/bgp/peer-route-policy/profile {
                        must "deref(current())/../../dc-route-policy-type = 'tenant'" {
                            tailf:dependency ".";
                            error-message
                              "Route policy type should be tenant.";
                        }

                        must "deref(current())/../../tenant = current()/../../../../tenant" {
                            tailf:dependency ".";
                            error-message
                              "Route policy tenant should be match with bridge-domain tenant.";
                        }
                    }

                    refine routing/bgp/source-interface/fabric-internal-connection/node/loopback-id {
                        must "count(current()/../../../../../../routing/bgp[peer-address != current()/../../../../peer-address]"
                                +   "/source-interface/fabric-internal-connection/node[leaf-id = current()/../leaf-id]/loopback-id = current()) = 0" {
                            error-message
                              "Loopback-id is already used in the device for another bgp peer under the same tenant and same bridge-domain.";
                        }                    

                        must "count(current()/../../../../../../../bridge-domain[name != current()/../../../../../../name]/routing/bgp[peer-address != current()/../../../../peer-address]"
                                +   "/source-interface/fabric-internal-connection/node[leaf-id = current()/../leaf-id]/loopback-id = current()) = 0" {
                            error-message
                              "Loopback-id is already used in the device for another bgp peer under the same tenant but different bridge-domain.";
                        }

                        must "count(current()/../../../../../../../../tenant-service[name != current()/../../../../../../../name]/bridge-domain/routing/bgp"
                                +   "/source-interface/fabric-internal-connection/node[leaf-id = current()/../leaf-id]/loopback-id = current()) = 0" {
                            error-message
                              "Loopback-id is already used in the device for another bgp peer under a different tenant.";
                        }
                    }
                }
            }
        }

        list port-configs {
            tailf:info "Deploy port groups configurations.";
            description
              "List of port groups definitions";

            key name;

            uses port-configs;

            list port-config {
                tailf:info "Deploy different type of port services [ethernet, port-channel, virtual-port-channel].";
                description
                  "Deploy different type of port services [ethernet, port-channel, virtual-port-channel]";

                uses ncs:nano-plan-data;
                uses ncs:service-data;
                ncs:servicepoint port-config-servicepoint;

                key name;

                uses port-config-service;
            }
        }

        list vrf-config {
            tailf:info "Vrf config service for VXLAN-EVPN configurations.";
            description
              "Vrf config service for VXLAN-EVPN configurations.";

            uses ncs:nano-plan-data;
            uses ncs:service-data;
            ncs:servicepoint vrf-config-servicepoint;
            key name;

            uses vrf-config-service;

            uses l3out-routing {
                refine routing/l3out-type {
                    default fabric-external;
                }

                refine routing/bgp/peer-route-policy/profile {
                    must "deref(current())/../../dc-route-policy-type = 'vrf'" {
                        tailf:dependency ".";
                        error-message
                          "Route policy type should be vrf.";
                    }

                    must "deref(current())/../../vrf = current()/../../../../name" {
                        tailf:dependency ".";
                        error-message
                          "Route policy vrf should be match with applied vrf.";
                    }
                }
            }
        }

        list dc-route-policy {
            tailf:info "Deploy tenant policy service";
            description
              "Datacenter route-policies for VXLAN-EVPN configurations.";

            uses ncs:service-data;
            ncs:servicepoint route-policy-config-servicepoint;

            key name;

            uses routepolicy-service;
        }
    }

    container dc-actions {
        tailf:info "Supported DC actions";
        description
          "Supported DC actions";

        container resource-pools {
            tailf:action create-site-resource-pools {
                tailf:actionpoint create-site-resource-pools;
                description
                  "Action to create resource-pools for selected site";
                input {
                    list id-pool {
                        key "id";

                        leaf id {
                            tailf:info "Pool Name. Can be l2-vxlan-vni | l3-vxlan-vni | network-vlan | vrf-vlan";
                            type enumeration {
                                enum l2-vxlan-vni;
                                enum l3-vxlan-vni;
                                enum l2-network-vlan;
                                enum l3-vrf-vlan;
                                enum port-channel-id;
                                enum fabric-external-l3-vrf-vlan;
                            }
                        }

                        leaf start {
                            type uint32;
                            mandatory true;
                        }

                        leaf end {
                            type uint32;
                            mandatory true;
                            must ". >= ../start" {
                                error-message
                                  "range end must be greater or equal to range start";
                                tailf:dependency "../start";
                            }
                        }

                        leaf scope {
                            tailf:info "Id Pool Scope. Can be fabric | local";
                            type enumeration {
                                enum fabric;
                                enum local;
                            }
                        }
                    }

                    leaf site {
                        tailf:info "Site name";
                        type leafref {
                            path "/cisco-dc:dc-site/cisco-dc:fabric";
                        }
                    }
                }

                output {
                    leaf success {
                        type boolean;
                    }
                }
            }
        }

        container port-configs {
            tailf:hidden "dc";
            tailf:action bridge-domain-redeploy {
                description
                  "Action to redeploy attached bridge-domains after a port is created or deleted";
                tailf:actionpoint bridge-domain-redeploy;
                input {
                    uses kicker:action-input-params;
                }
                output {
                }
            }
        }
    }
}
