submodule cisco-dc-l3out-routing {
    belongs-to cisco-dc {
        prefix "cisco-dc";
    }

    yang-version 1.1;

    import ietf-inet-types {
        prefix inet;
    }

    import tailf-common {
        prefix tailf;
    }

    import tailf-ncs {
        prefix ncs;
    }

    include cisco-dc-common {
        revision-date "2022-01-17";
    }

    revision 2022-01-17 {
        description
          "Initial Revision.";
    }

    grouping l3out-routing {
        container routing {
            tailf:info "Specify routing details";

            leaf l3out-type {
                tailf:hidden "dc";
                type enumeration {
                    enum fabric-external;
                    enum fabric-internal;
                }
            }

            list bgp {
                tailf:info "Define bgp routes";
                key peer-address;

                leaf peer-address {
                    tailf:info "Specify peer address value";
                    type inet:ip-address;
                }

                container source-interface {
                    tailf:info "Attach source interface connection";

                    container fabric-external-connection {
                        when "../../../l3out-type = 'fabric-external'";
                        tailf:info "attach external connection";
                        tailf:cli-drop-node-name;

                        leaf node {
                            must "/cisco-dc:dc-site[cisco-dc:fabric=current()/../../../../../site]"
                                    +   "/cisco-dc:node[cisco-dc:hostname=current()]/cisco-dc:node-role = 'border-leaf'" {
                                error-message
                                  "Node role must be border-leaf";
                            }

                            tailf:info "Node name";
                            type leafref {
                                path "/cisco-dc:dc-site[cisco-dc:fabric=current()/../../../../../site]"
                                        + "/cisco-dc:node/cisco-dc:hostname";
                            }
                            mandatory true;
                        }

                        leaf connection {
                            tailf:info "Fabric l3out uplink can be uplink-to-dci-gw-01 or uplink-to-dci-gw-02";
                            type enumeration {
                                enum uplink-to-dci-gw-01;
                                enum uplink-to-dci-gw-02;
                            }
                            mandatory true;
                        }

                        leaf address {
                            tailf:hidden "dc";
                            type tailf:ip-address-and-prefix-length;
                        }

                        leaf vlan {
                            tailf:hidden "dc";
                            type vlan;
                        }

                        leaf port-channel-id {
                            tailf:hidden "dc";
                            type uint16 {
                                range "500..600";
                            }
                        }
                    }

                    container fabric-internal-connection {
                        when "../../../l3out-type = 'fabric-internal'";
                        tailf:info "attach internal connection";
                        tailf:cli-drop-node-name;

                        list node {
                            tailf:info "Associate bgp routing on loopback";
                            key "leaf-id";

                            leaf leaf-id {
                                must "/cisco-dc:dc-site[cisco-dc:fabric=current()/../../../../../../site]"
                                        +   "/cisco-dc:node[cisco-dc:hostname=current()]/cisco-dc:node-role = 'access-leaf'" {
                                    error-message
                                      "Node role must be access-leaf";
                                }

                                tailf:info "Node name";
                                type leafref {
                                    path "/cisco-dc:dc-site[cisco-dc:fabric=current()/../../../../../../site]"
                                        + "/cisco-dc:node/cisco-dc:hostname";
                                }
                                mandatory true;
                            }

                            leaf loopback-id {
                                tailf:info "Specify loopback id";
                                type loopback-id;
                            }

                            leaf address {
                                tailf:info "A.B.C.D/L;;Prefix or X:X::X/L;;Prefix for Loopback";
                                type tailf:ip-address-and-prefix-length;
                                mandatory true;
                            }
                        }
                    }
                }

                leaf remote-as {
                    tailf:info "Specify remote asn number";
                    type uint32;
                    mandatory true;
                }

                leaf local-as {
                    tailf:info "Specify local asn number";
                    type uint32;
                }

                leaf-list peer-af-controls {
                    tailf:info "Peer address family controls";
                    type enumeration {
                        enum send-com;
                        enum nh-self;
                        enum dis-peer-as-check;
                        enum allow-self-as;
                        enum as-override;
                    }
                }

                leaf peer-control {
                    tailf:info "Peer control";
                    type enumeration {
                        enum dis-conn-check;
                        enum bfd;
                    }
                }

                leaf password {
                    tailf:info "Specify the BGP password";
                    type tailf:aes-cfb-128-encrypted-string;
                }

                leaf weight {
                    tailf:info "Specify weight";
                    type uint16;
                }

                leaf ttl {
                    tailf:info "Specify ttl value";
                    type uint8;
                }

                list peer-route-policy {
                    tailf:info "Attach route policy name, please make sure, its defined under dc-route-policy";
                    key direction;

                    leaf direction {
                        tailf:info "Define direction on route-policy";
                        type enumeration {
                            enum "in";
                            enum "out";
                        }
                    }

                    leaf profile {
                        tailf:info "Route-policy name";
                        type leafref {
                            path "/cisco-dc:dc-site[cisco-dc:fabric=current()/../../../../site]"
                            +   "/cisco-dc:dc-route-policy/cisco-dc:route-policy/cisco-dc:profile";
                        }
                    }
                }

                container timers {
                    tailf:info "Specify keepalive and hold timers";
                    presence
                      true;
                    leaf keepalive {
                        type uint16;
                        default 8;
                    }

                    leaf holdtime {
                        type uint16;
                        default 24;
                    }

                    must "number(current()/keepalive) < number(current()/holdtime)" {
                        error-message
                          "Hold time must be greater that keepalive time";
                    }
                }

                leaf as-number {
                    tailf:hidden "Just for convenience";
                    type inet:as-number;
                }

                leaf address-family {
                    tailf:info "BGP address-family can be IPv4 | IPv6";
                    tailf:hidden "dc";
                    type enumeration {
                        enum ipv4;
                        enum ipv6;
                    }
                }

                leaf vrf {
                    tailf:hidden "Just for convenience";
                    type string;
                }
            }

            container static-route {
                when "../l3out-type = 'fabric-internal'";
                tailf:info "Define static routes";
                presence
                  true;

                list destination {
                    tailf:info "Define ip destination";
                    key address;

                    leaf address {
                        tailf:info "A.B.C.D/L;;Prefix or X:X::X/L;;Prefix of static route to add";
                        type inet:ip-prefix;
                    }

                    leaf ip-nexthop {
                        tailf:info "A.B.C.D;; or X:X::X;; static route to add ip-nexthop";
                        type inet:ip-address;
                        mandatory true;
                    }

                    container source-node {
                        tailf:info "Attach source node connection\n"
                        +   "it can be either fabric external connection OR fabric internal connection";

                        choice template {
                            mandatory true;

                            case apply-specific-nodes {
                                container apply-specific-nodes {
                                    tailf:info "Configurations are created with selecting nodes by operator";

                                    list node {
                                        tailf:info "Attach access leaf node";
                                        key "leaf-id";

                                        leaf leaf-id {
                                            must "/cisco-dc:dc-site[cisco-dc:fabric=current()/../../../../../../../site]"
                                            +   "/cisco-dc:node[cisco-dc:hostname=current()]/cisco-dc:node-role = 'access-leaf'" {
                                                error-message
                                                  "Node role must be access-leaf";
                                            }

                                            must "/cisco-dc:dc-site[cisco-dc:fabric=current()/../../../../../../../site]"
                                            +   "/cisco-dc:node[cisco-dc:hostname=current()]/cisco-dc:node-type = 'standalone'" {
                                                error-message
                                                  "Node type must be standalone";
                                            }

                                            tailf:info "Node name";
                                            type leafref {
                                                path "/cisco-dc:dc-site[cisco-dc:fabric=current()/../../../../../../../site]"
                                                + "/cisco-dc:node/cisco-dc:hostname";
                                            }
                                        }
                                    }

                                    list node-group {
                                        tailf:info "Attach vpc node-group";
                                        key id;

                                        leaf id {
                                            tailf:info "Node group id";
                                            type leafref {
                                                path "/cisco-dc:dc-site[cisco-dc:fabric=current()/../../../../../../../site]"
                                                +   "/cisco-dc:node-group/cisco-dc:id";
                                            }
                                        }
                                    }
                                }
                            }

                            case apply-all-nodes {
                                leaf apply-all-nodes {
                                    tailf:info "Configurations are applied to all bridge-domain nodes by ncs";
                                    type empty;
                                }
                            }
                        }

                        list device {
                            tailf:hidden "Attach device defined in infra";
                            key "kp leaf-id";

                            leaf kp {
                                tailf:info "Attach vrf or bd keypath";
                                type string;
                            }

                            leaf leaf-id {
                                tailf:info "Define Leaf Node ID";
                                type string;
                            }

                            leaf ip-nexthop {
                                tailf:info "A.B.C.D;; or X:X::X;; static route to add ip-nexthop";
                                type inet:ip-address;
                            }

                            leaf address-family {
                                tailf:info "Static Route address-family can be IPv4 | IPv6";
                                type enumeration {
                                    enum ipv4;
                                    enum ipv6;
                                }
                            }
                        }
                    }

                    leaf address-family {
                        tailf:info "Static Route address-family can be IPv4 | IPv6";
                        tailf:hidden "dc";
                        type enumeration {
                            enum ipv4;
                            enum ipv6;
                        }
                    }

                    leaf vrf {
                        tailf:hidden "Just for convenience";
                        type string;
                    }
                }
            }
        }
    }
}
