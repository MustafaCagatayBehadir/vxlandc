submodule cisco-dc-port-config {
    belongs-to cisco-dc {
        prefix "cisco-dc";
    }

    yang-version 1.1;

    import tailf-common {
        prefix tailf;
    }

    import tailf-ncs {
        prefix ncs;
    }

    include cisco-dc-common {
        revision-date "2022-01-17";
    }

    revision 2022-01-17 {
        description
          "Initial Revision.";
    }

    grouping port-configs {

        leaf name {
            tailf:info "Port Group Name";
            type dc-string;
        }

        leaf mode {
            tailf:info "Port Group Mode can be Access or Trunk";
            type enumeration {
                enum access;
                enum trunk;
            }
            mandatory true;
        
            must "not(../port-config/mode) or current() = ../port-config/mode" {
                error-message
                  "Port group mode can't be changed if it has ports under it.";
            }
        }

        list attached-bridge-domain {
            tailf:info "Attach bridge-domain defined in infra by bridge-domain service";
            config false;
            tailf:cdb-oper {
                tailf:persistent true;
            }

            key "site tenant bridge-domain";

            leaf site {
                tailf:info "Site name";
                type leafref {
                    path "../../../cisco-dc:fabric";
                }
            }

            leaf tenant {
                tailf:info "Tenant name";
                type leafref {
                    path "../../../cisco-dc:tenant-service/cisco-dc:name";
                }
            }

            leaf bridge-domain {
                tailf:info "Bridge domain name";
                type leafref {
                    path "deref(../tenant)/../cisco-dc:bridge-domain/cisco-dc:name";
                }
            }
        }

        leaf-list attached-bridge-domain-kp {
            tailf:hidden "dc";
            type string;
        }

        leaf-list attached-ports {
            tailf:info "Attached port-config name";
            config false;
            tailf:cdb-oper {
                tailf:persistent true;
            }
            type dc-string;
        }
    }

    grouping port-config-service {

        leaf name {
            tailf:info "Port Name";
            tailf:cli-allow-range;
            type dc-string;
        }

        leaf description {
            tailf:info "This description is auto-generated, use this field to overwrite the default behavior.";
            type string {
                length "1..254";
            }
        }

        leaf connection {
            tailf:info "Connection type can be host or switch";
            type enumeration {
                enum host;
                enum switch;
            }
            mandatory true;
        }

        leaf speed {
            tailf:info "Port Speed";
            type enumeration {
                enum 1G;
                enum 10G;
                enum 25G;
                enum 40G;
                enum 100G;
            }
            mandatory true;
        }

        choice port-type {
            mandatory true;

            case ethernet {
                container ethernet {
                    when "not(current()/../port-channel) and not(current()/../vpc-port-channel)";
                    tailf:info "Single Attach Port Type";

                    leaf node-copy {
                        tailf:info "only to suppress compiler warning on must expression";
                        type string;
                        tailf:hidden "dc";
                    }

                    leaf node {
                        must "/cisco-dc:dc-site[cisco-dc:fabric=current()/../../site]" 
                             + "/cisco-dc:node[cisco-dc:hostname=current()]/cisco-dc:node-role = 'access-leaf'" {
                            error-message
                              "Node type must be access-leaf";
                        }

                        must "not(../node-copy) or ../node-copy = ." {
                            error-message
                              "Node can't be changed ones the port is deployed";
                        }

                        tailf:info "Node Name";
                        type leafref {
                            path "/cisco-dc:dc-site[cisco-dc:fabric=current()/../../site]"
                                 + "/cisco-dc:node/cisco-dc:hostname";
                        }
                        mandatory true;
                    }

                    leaf-list node-port-copy {
                        tailf:info "only to suppress compiler warning on must expression";
                        type string;
                        tailf:hidden "dc";
                    }

                    leaf-list node-port {
                        tailf:info "Node Port Id List";
                        type node-port;
                        min-elements 1;

                        must "not(../node-port-copy) or ../node-port-copy = ." {
                            error-message
                              "Node-port can't be changed ones the port is deployed";
                        }
                    }
                }
            }

            case port-channel {
                container port-channel {
                    when "not(current()/../ethernet) and not(current()/../vpc-port-channel)";
                    tailf:info "Port Channel Port Type";

                    leaf port-channel-id {
                        tailf:info "Port Channel Id is auto-generated, use this field to overwrite the default behavior.";
                        type uint16 {
                            range "1..500";
                        }
                    }

                    leaf allocated-port-channel-id {
                        tailf:hidden "Just for convenience";
                        type uint16 {
                            range "1..500";
                        }
                    }

                    leaf node-copy {
                        tailf:info "only to suppress compiler warning on must expression";
                        type string;
                        tailf:hidden "dc";
                    }

                    leaf node {
                        must "/cisco-dc:dc-site[cisco-dc:fabric=current()/../../site]" 
                             + "/cisco-dc:node[cisco-dc:hostname=current()]/cisco-dc:node-role = 'access-leaf'" {
                            error-message
                              "Node type must be access-leaf";
                        }

                        must "not(../node-copy) or ../node-copy = ." {
                            error-message
                              "Node can't be changed ones the port is deployed";
                        }

                        tailf:info "Node Name";
                        type leafref {
                            path "/cisco-dc:dc-site[cisco-dc:fabric=current()/../../site]"
                                 + "/cisco-dc:node/cisco-dc:hostname";
                        }
                    }

                    leaf-list node-port {
                        tailf:info "Node Port Id List";
                        type node-port;
                        min-elements 1;
                    }
                }
            }

            case vpc-port-channel {
                container vpc-port-channel {
                    when "not(current()/../ethernet) and not(current()/../port-channel)";
                    tailf:info "VPC Port Channel Port Type";

                    leaf port-channel-id {
                        tailf:info "Port Channel Id is auto-generated, use this field to overwrite the default behavior.";
                        type uint16 {
                            range "1..500";
                        }
                    }

                    leaf allocated-port-channel-id {
                        tailf:hidden "Just for convenience";
                        type uint16 {
                            range "1..500";
                        }
                    }

                    leaf node-group-copy {
                        tailf:info "only to suppress compiler warning on must expression";
                        type string;
                        tailf:hidden "dc";
                    }

                    leaf node-group {

                        must "not(../node-group-copy) or ../node-group-copy = ." {
                            error-message
                              "Node-Group can't be changed ones the port is deployed";
                        }

                        tailf:info "Node Group Name";
                        type leafref {
                            path "/cisco-dc:dc-site[cisco-dc:fabric=current()/../../site]"
                                 + "/cisco-dc:node-group/cisco-dc:id";
                        }
                        mandatory true;
                    }

                    leaf-list node-1-port {
                        tailf:info "Node 1 Port List";
                        type node-port;
                        min-elements 1;
                    }

                    leaf-list node-2-port {
                        tailf:info "Node 2 Port List";
                        type node-port;
                        min-elements 1;
                    }

                    list node {
                        tailf:hidden "dc";

                        key name;

                        leaf name {
                            tailf:info "Define Leaf Node ID";
                            type string;
                        }

                        leaf allocated-port-channel-id {
                            type uint16 {
                                range "1..500";
                            }
                            tailf:default-ref "../../allocated-port-channel-id";
                        }

                        leaf-list node-port {
                            tailf:info "Define Interface ID example: 1/19";
                            type node-port;
                        }
                    }
                }
            }
        }

        leaf shutdown {
            tailf:info "Port administratively down";
            type empty;
        }

        leaf storm-control-action {
            tailf:info "Storm control action can be trap | shutdown";
            tailf:cli-show-with-default;
            type enumeration {
                enum trap;
                enum shutdown;
            }
            default shutdown;
        }

        leaf auto-bum {
            tailf:info "BUM is auto-generated based on port speed.";
            tailf:cli-show-config;
            config false;
            type decimal64 {
                fraction-digits 2;
                range "0.0..100.0";
            }
        }

        leaf bum {
            tailf:info "BUM is auto-generated, use this field to overwrite the default behavior.";
            type decimal64 {
                fraction-digits 2;
                range "0.0..100.0";
            }
        }

        leaf site {
            tailf:hidden "Just for convenience";
            type string;
            tailf:default-ref "../../../cisco-dc:fabric";
        }

        leaf mode {
            tailf:hidden "dc";
            type string;
        }

        leaf-list vlan {
            tailf:info "Vlan id list for port.";
            type vlan;
            tailf:hidden "dc";
        }

        leaf port-group {
            tailf:hidden "Just for convenience";
            type string;
            tailf:default-ref "../../name";
        }

        leaf-list attached-bridge-domain-kp {
            tailf:hidden "dc";
            type string;
        }

        leaf type {
            tailf:hidden "dc";
            type string;
        }

        leaf id-allocated {
            tailf:hidden "dc";
            type boolean;
            default false;
        }

        leaf approved {
            tailf:info "Approved will set to true if id is allocated";
            type boolean;
            default false;
        }
    }
}
