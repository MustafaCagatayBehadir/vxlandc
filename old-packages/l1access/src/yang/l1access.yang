module l1access {

    yang-version 1.1;
    namespace "http://turkcell.com.tr/l1access";
    prefix l1access;

    import ietf-inet-types {
        prefix inet;
    }
    import tailf-common {
        prefix tailf;
    }
    import tailf-ncs {
        prefix ncs;
    }
    import vxlandc-core {
        prefix vxlandc-core;
    }

    description
      "VXLAN EVPN Datacenter physical RFS service";

    revision 2022-01-17 {
        description
          "Initial revision.";
    }

    typedef node-port {
        type string {
            pattern
              '[1-9]/[1-9][0-9]{0,1}';
        }
    }

    identity id-allocated {
        base ncs:plan-state;
    }

    identity l1-fabric-service-configured {
        base ncs:plan-state;
    }

    ncs:plan-outline l1-fabric-service-plan {
        description
          "L1 Fabric Service Plan";

        ncs:component-type "ncs:self" {
            ncs:state "ncs:init";

            ncs:state "l1access:id-allocated" {
                ncs:create {
                    ncs:nano-callback;
                }
            }

            ncs:state "l1access:l1-fabric-service-configured" {
                ncs:create {
                    ncs:pre-condition {
                        ncs:all {
                            ncs:monitor  "$SERVICE/plan/component[type='ncs:self'][name='self']/state[name='l1access:id-allocated']" {
                                ncs:trigger-expr "status = 'reached'";
                            }
                            ncs:monitor "$SERVICE" {
                                ncs:trigger-expr "approved = 'true'";
                            }
                        }
                    }
                    ncs:nano-callback;
                }
            }
            ncs:state "ncs:ready";
        }
    }

    ncs:service-behavior-tree l1-fabric-service-servicepoint {
        description
          "L1 Fabric Service Behavior Tree";
        ncs:plan-outline-ref "l1-fabric-service-plan";

        ncs:selector {
            ncs:create-component "'self'" {
                ncs:component-type-ref "ncs:self";
            }
        }
    }

    grouping port-groups {
        container port-groups {
            description
              "Tenant Physical Attachmnets Groups";
            tailf:info "Tenant Physical Attachments Groups";

            list port-group {
                key "name";

                leaf name {
                    tailf:info "Port Group Name";
                    type string;
                }

                leaf-list port {
                    must "deref(current())/../mode = ../mode" {
                        error-message
                          "Port mode has to be same as port group mode";
                        tailf:dependency ".";
                        tailf:dependency "../mode";
                    }
                    tailf:info "Ports belongs to port group";
                    type leafref {
                        path "../../../l1access:ports/l1access:port/l1access:name";
                    }
                }

                leaf mode {
                    tailf:info "Port Group Mode can be Access or Trunk";
                    type enumeration {
                        enum access;
                        enum trunk;
                    }
                    mandatory true;
                }
            }
        }
    }

    grouping ports {

        container ports {
            description
              "Tenant Physical Attachmnets";
            tailf:info "Tenant Physical Attachments Configurations";

            list port {

                uses ncs:nano-plan-data;
                uses ncs:service-data;
                ncs:servicepoint l1-fabric-service-servicepoint;

                key name;

                leaf name {
                    tailf:info "Unique ID for this physicalAttachment.  May contain Service ID";
                    type string;
                }

                leaf description {
                    tailf:info "This description is auto-generated, use this field to overwrite the default behavior.";
                    type string {
                        length "1..254";
                    }
                }

                leaf mode {
                    tailf:info "Port Mode can be Access or Trunk";
                    type enumeration {
                        enum access;
                        enum trunk;
                    }
                    mandatory true;
                }

                leaf connection {
                    tailf:info "Connection type can be host or switch";
                    type enumeration {
                        enum host;
                        enum switch;
                    }
                    mandatory true;
                }

                leaf speed {
                    tailf:info "Port Speed";
                    type enumeration {
                        enum 1G;
                        enum 10G;
                        enum 25G;
                        enum 40G;
                        enum 100G;
                    }
                    mandatory true;
                }

                leaf shutdown {
                    tailf:info "Port administratively down";
                    type empty;
                }

                leaf storm-control-action-trap {
                    tailf:info "Change storm control action to trap";
                    type empty;
                }

                leaf site {
                    tailf:hidden "Just for convenience";
                    type string;
                    tailf:default-ref "../../../../../vxlandc-core:fabric";
                }

                leaf tenant {
                    tailf:hidden "Just for convenience";
                    type string;
                    tailf:default-ref "../../../vxlandc-core:name";
                }

                leaf type {
                    tailf:hidden "Just for convenience";
                    type string;
                }

                choice port-type {
                    mandatory true;
                    case ethernet {
                        container ethernet {
                            tailf:info "Single Attach Port Type";

                            leaf node {
                                must "/vxlandc-core:vxlandc/vxlandc-core:sites/vxlandc-core:site[vxlandc-core:fabric=current()/../../site]" 
                                + "/vxlandc-core:node[vxlandc-core:hostname=current()]/vxlandc-core:node-role = 'access-leaf'" {
                                    error-message
                                      "Node type must be access-leaf";
                                }
                                tailf:info "Node Name";
                                type leafref {
                                    path "/vxlandc-core:vxlandc/vxlandc-core:sites/vxlandc-core:site[vxlandc-core:fabric=current()/../../site]"
                                    + "/vxlandc-core:node/vxlandc-core:hostname";
                                }
                                mandatory true;
                            }

                            leaf-list node-port {
                                tailf:info "Node Port Id List";
                                type node-port;
                                min-elements 1;
                            }

                            leaf node-port-flat {
                                config false;
                                tailf:cdb-oper {
                                    tailf:persistent true;
                                }
                                tailf:info "Flat structure of the Node Port";
                                type string;
                            }
                        }
                    }
                    case port-channel {
                        container port-channel {
                            tailf:info "Port Channel Port Type";

                            leaf port-channel-id {
                                tailf:info "Port Channel Id is auto-generated, use this field to overwrite the default behavior.";
                                type uint16 {
                                    range "1..500";
                                }
                            }

                            leaf allocated-port-channel-id {
                                tailf:hidden "Just for convenience";
                                type uint16 {
                                    range "1..500";
                                }
                            }

                            leaf node {
                                must "/vxlandc-core:vxlandc/vxlandc-core:sites/vxlandc-core:site[vxlandc-core:fabric=current()/../../site]" 
                                + "/vxlandc-core:node[vxlandc-core:hostname=current()]/vxlandc-core:node-role = 'access-leaf'" {
                                    error-message
                                      "Node type must be access-leaf";
                                }
                                tailf:info "Node Name";
                                type leafref {
                                    path "/vxlandc-core:vxlandc/vxlandc-core:sites/vxlandc-core:site[vxlandc-core:fabric=current()/../../site]"
                                    + "/vxlandc-core:node/vxlandc-core:hostname";
                                }
                            }

                            leaf-list node-port {
                                tailf:info "Node Port Id List";
                                type node-port;
                                min-elements 1;
                            }

                            leaf node-port-flat {
                                config false;
                                tailf:cdb-oper {
                                    tailf:persistent true;
                                }
                                tailf:info "Flat structure of the Node Port";
                                type string;
                            }
                        }
                    }
                    case vpc-port-channel {
                        container vpc-port-channel {
                            tailf:info "VPC Port Channel Port Type";

                            leaf port-channel-id {
                                tailf:info "Port Channel Id is auto-generated, use this field to overwrite the default behavior.";
                                type uint16 {
                                    range "1..500";
                                }
                            }

                            leaf allocated-port-channel-id {
                                tailf:hidden "Just for convenience";
                                type uint16 {
                                    range "1..500";
                                }
                            }

                            leaf node-group {
                                tailf:info "Node Group Name";
                                type leafref {
                                    path "/vxlandc-core:vxlandc/vxlandc-core:sites/vxlandc-core:site[vxlandc-core:fabric=current()/../../site]"
                                    + "/vxlandc-core:node-group/vxlandc-core:id";
                                }
                                mandatory true;
                            }

                            leaf-list node-1-port {
                                tailf:info "Node 1 Port List";
                                type node-port;
                                min-elements 1;
                            }

                            leaf-list node-2-port {
                                tailf:info "Node 2 Port List";
                                type node-port;
                                min-elements 1;
                            }

                            leaf node-1-port-flat {
                                config false;
                                tailf:cdb-oper {
                                    tailf:persistent true;
                                }
                                tailf:info "Flat structure of the Node 1 Port";
                                type string;
                            }

                            leaf node-2-port-flat {
                                config false;
                                tailf:cdb-oper {
                                    tailf:persistent true;
                                }
                                tailf:info "Flat structure of the Node 2 Port";
                                type string;
                            }
                        }
                    }
                }

                leaf approved {
                    tailf:info "Approved will set to true if id is allocated";
                    type boolean;
                    default false;
                }
            }
        }
    }

    augment "/vxlandc-core:vxlandc/vxlandc-core:sites/vxlandc-core:site/vxlandc-core:tenants/vxlandc-core:tenant" {
        uses port-groups;
        uses ports;
    }
}
