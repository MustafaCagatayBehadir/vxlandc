submodule cisco-dc-site {

    belongs-to cisco-dc {
        prefix "cisco-dc";
    }

    yang-version 1.1;

    import ietf-inet-types {
        prefix inet;
    }

    import tailf-common {
        prefix tailf;
    }

    import tailf-ncs {
        prefix ncs;
    }

    import resource-allocator {
        prefix ralloc;
    }

    import id-allocator {
        prefix idalloc;
    }

    description
      "VXLAN EVPN Datacenter Environment";

    revision 2022-01-17 {
        description
          "Initial revision.";
    }

    grouping site-configs {

        leaf fabric {
            tailf:info "Data Center Fabric Name";
            type string;
        }

        list node {
            tailf:info "Deploy Fabric Node Configurations";
            key hostname;

            leaf hostname {
                tailf:info "Node hostname";
                type leafref {
                    path "/ncs:devices/ncs:device/ncs:name";
                }
            }

            leaf node-role {
                tailf:info "Node role in the fabric";
                type enumeration {
                    enum access-leaf;
                    enum border-leaf;
                    enum spine;
                }
                mandatory true;
            }

            leaf node-type {
                when "../node-role != 'spine'";
                tailf:info "Node type can be vpc or standalone";
                type enumeration {
                    enum standalone;
                    enum vpc;
                }
                mandatory true;
            }

            leaf vpc-id {
                when "../node-type = 'vpc'";
                tailf:info "vPC domain id";
                type uint16 {
                    range "1..1000";
                }
                mandatory true;
            }

            leaf po-id-pool {
                tailf:hidden "dc";
                tailf:info "Port Channel ID Pool Name";
                type leafref {
                    path "/ralloc:resource-pools/idalloc:id-pool/idalloc:name";
                }
            }
        }

        list node-group {
            tailf:info "Deploy Fabric vPC Node-Group Configurations";
            key id;
            unique "node-1";
            unique "node-2";

            leaf id {
                tailf:info "vPC Domain ID";
                type uint16 {
                    range "1..1000";
                }
                tailf:cli-suppress-range;
            }

            leaf node-1 {
                must "/cisco-dc:dc-site[cisco-dc:fabric=current()/../../cisco-dc:fabric]"
                     + "/cisco-dc:node[cisco-dc:hostname=current()]/cisco-dc:node-type = 'vpc'" {
                    error-message
                      "Node type must be vpc";
                }
                tailf:info "vpc Node 1 hostname";
                type leafref {
                    path "/ncs:devices/ncs:device/ncs:name";
                }
                mandatory true;
            }

            leaf node-2 {
                must "/cisco-dc:dc-site[cisco-dc:fabric=current()/../../cisco-dc:fabric]"
                     + "/cisco-dc:node[cisco-dc:hostname=current()]/cisco-dc:node-type = 'vpc'" {
                    error-message
                      "Node type must be vpc";
                }
                tailf:info "vpc Node 2 hostname";
                type leafref {
                    path "/ncs:devices/ncs:device/ncs:name";
                }
                mandatory true;
            }

            leaf po-id-pool {
                tailf:hidden "dc";
                tailf:info "Port Channel ID Pool Name";
                type leafref {
                    path "/ralloc:resource-pools/idalloc:id-pool/idalloc:name";
                }
            }
        }

        container connections {
            leaf uplink-to-dci-gw-01 {
                tailf:info "Port-Channel interface id on the border leaf to DCI-GW-01";
                type uint16 {
                    range "500..600";
                }
                mandatory true;
            }

            leaf uplink-to-dci-gw-02 {
                tailf:info "Port-Channel interface id on the border leaf to DCI-GW-02";
                type uint16 {
                    range "500..600";
                }
                mandatory true;
            }
        }

        container fabric-parameters {
            leaf as-number {
                tailf:info "BGP AS Number of the Site";
                type inet:as-number;
                mandatory true;
            }

            leaf mcast-group {
                tailf:info "Multicast Group for VXLAN Overlay";
                type inet:ipv4-address;
                mandatory true;
            }

            leaf internet-vrf {
                tailf:info "Fabric Internet VRF Name";
                type string;
                mandatory true;
            }

            container dci-reference {
                tailf:info "DCI reference device information for fabric route check.";

                leaf name {
                    tailf:info "Router hostname";
                    type string;
                    mandatory true;
                }

                leaf address {
                    tailf:info "Router ip address infromation";
                    type inet:ipv4-address;
                    mandatory true;
                }

                leaf authgroup {
                    tailf:info "Authentication credentials for the device";
                    type leafref {
                        path "/ncs:devices/ncs:authgroups/ncs:group/ncs:name";
                    }
                    mandatory true;
                }
            }
        }

        container resource-pools {
            tailf:hidden "dc";

            leaf l2-network-vlan {
                tailf:info "Layer 2 Network Vlan Pool";
                type leafref {
                    path "/ralloc:resource-pools/idalloc:id-pool/idalloc:name";
                }
            }

            leaf l3-vrf-vlan {
                tailf:info "Layer 3 VRF Vlan Pool";
                type leafref {
                    path "/ralloc:resource-pools/idalloc:id-pool/idalloc:name";
                }
            }

            leaf l2-vxlan-vni {
                tailf:info "Layer 2 VXLAN VNI Pool";
                type leafref {
                    path "/ralloc:resource-pools/idalloc:id-pool/idalloc:name";
                }
            }

            leaf l3-vxlan-vni {
                tailf:info "Layer 3 VXLAN VNI Pool";
                type leafref {
                    path "/ralloc:resource-pools/idalloc:id-pool/idalloc:name";
                }
            }

            leaf fabric-external-l3-vrf-vlan {
                tailf:info "Fabric External BGP option-A Vlan Pool";
                type leafref {
                    path "/ralloc:resource-pools/idalloc:id-pool/idalloc:name";
                }
            }
        }

        container validations {
            tailf:info "Fabric validations";
            presence
              true;

            leaf disable-port-config-validation {
                tailf:info "Turns off validation of port configs.";
                type empty;
            }

            leaf disable-bridge-domain-validation {
                tailf:info "Turns off validation for bridge-domains.";
                type empty;
            }
        }

        container migrations {
            tailf:info "This container will be deleted after the migrations.";
            presence true;

            leaf disable-overwrite {
                tailf:info "Turns off service overwrites.";
                type empty;
            }
        }
    }
}
